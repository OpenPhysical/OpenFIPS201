OpenFIPS201_GET_STATUS_Schema DEFINITIONS IMPLICIT TAGS ::= 
BEGIN

-- Raw GlobalPlatform Application lifecycle byte. OpenFIPS201 uses application-specific
-- value 0x0F for its personalised state; other platform-defined values remain valid.
AppletState ::= INTEGER (0..255)

GetStatusResponse ::= [APPLICATION 19] SEQUENCE {
	appletState		[0] AppletState,
	pinVerified		[1] BOOLEAN,
	pinAlways		[2] BOOLEAN,
	smState			[3] BOOLEAN,
	vciState		[4] BOOLEAN,
	scpState		[5] BOOLEAN,
	contactless		[6] BOOLEAN,
	fipsMode		[7] BOOLEAN
}

END
